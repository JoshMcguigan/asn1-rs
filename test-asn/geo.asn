Geometry DEFINITIONS ::= BEGIN

Unsigned16 ::= INTEGER (0..65535)

Point ::= SEQUENCE {
	x	INTEGER,
	y	INTEGER
}

Line ::= SEQUENCE {
	p1	Point,
	p2	Point
}

Rectangle ::= SEQUENCE {
	width	INTEGER (0..18446744073709551615),
	height	INTEGER (0..18446744073709551615)
}

TinyRectangle ::= SEQUENCE {
	width	INTEGER (0..255),
	height	INTEGER (0..255)
}

SmallRectangle ::= SEQUENCE {
	width	Unsigned16,
	height	Unsigned16
}

END
